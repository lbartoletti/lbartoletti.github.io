FME workspace fme_test_intersects.fmw

Parameters:
- DestDataset_CSV2 = $(FME_MF_DIR)sortie_fme   # Destination CSV (Comma Separated Value) Folder
- DestDataset_CSV2_3 = $(FME_MF_DIR)sortie_fme   # Destination CSV (Comma Separated Value) Folder

Writers:
- CSV2_1: CSV2 to $(DestDataset_CSV2)
- CSV2_2: CSV2 to $(DestDataset_CSV2_3)

Creator_2
    GEOMTYPE = Geometry Object
    NUM = 1
    CREATED -> Line
Line: GeometryReplacer
    KIND_LONG = Hex Encoded OGC Well Known Binary
    REMOVE_ATTRIBUTE = Yes
    SOURCE = 010200000002000000ea9c6d2b873c3e41a03d941b7cd5534133db7796ce3c3e413fba569864d55341
    -> SpatialFilter [Filter]
    -> LineOnLineOverlayer [LINE]
Creator
    GEOMTYPE = Geometry Object
    NUM = 1
    CREATED -> Base
Base: GeometryReplacer
    KIND_LONG = Hex Encoded OGC Well Known Binary
    REMOVE_ATTRIBUTE = Yes
    SOURCE =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
    -> SpatialFilter [Filter]
    -> LineOnLineOverlayer [LINE]
LineOnLineOverlayer
    ATTRS_ACCUM_MODE = Use Attributes From One Feature
    CLEANING_TOLERANCE = Automatic
    DEAGGREGATE_INPUT = Yes
    GENERATE_LIST_DROP = NO
    OV_ATTR = _overlaps
    SEPARATE_COLLINEAR_SEGMENTS = No
    POINT -> GeometryExtractor
    POINT -> GeometryExtractor_2
    POINT -> SpatialFilter [Candidate]
GeometryExtractor
    ATTR = wkt_64bits
    KIND_LONG = OGC Well Known Text
    OGCVERSION = 1.2
    OGC_WKT_PRECISION_DISPLAY = 64-bit
    REMOVE_GEOMETRY = No
    -> wkt (writer CSV2_1)
wkt (writer CSV2_1)
    attributes: _creation_instance uint64, _overlaps uint32, wkt_64bits string
GeometryExtractor_2
    ATTR = wkb
    KIND_LONG = OGC Well Known Binary
    OGCVERSION = 1.2
    REMOVE_GEOMETRY = No
    -> wkb (writer CSV2_2)
wkb (writer CSV2_2)
    attributes: _creation_instance uint64, _overlaps uint32, wkb string
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> Failed
Failed: Inspector
